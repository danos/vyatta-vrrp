module vyatta-op-show-vrrp-v1 {
    namespace "urn:vyatta.com:mgmt:vyatta-op-show-vrrp:1";
    prefix vyatta-op-show-vrrp-v1;

    import vyatta-opd-extensions-v1 {
        prefix opd;
    }
    import vyatta-op-show-v1 {
        prefix show;
    }
    import vyatta-op-show-log-v1 {
        prefix log;
    }

    organization "AT&T Inc.";
    contact
        "AT&T
        Postal: 208 S. Akard Street
        Dallas, TX 75202
        E-mail: DL-vyatta-help@att.com
        Web: www.att.com";

    description
        "Copyright (c) 2020, AT&T Intellectual Property.
         All rights reserved.

         Defines operational CLI for show commands related to VRRP.

        Redistribution and use in source and binary forms, with or without
        modification, are permitted provided that the following conditions
        are met:

        1. Redistributions of source code must retain the above copyright
           notice, this list of conditions and the following disclaimer.
        2. Redistributions in binary form must reproduce the above
           copyright notice, this list of conditions and the following
           disclaimer in the documentation and/or other materials provided
           with the distribution.
        3. Neither the name of the copyright holder nor the names of its
           contributors may be used to endorse or promote products derived
           from this software without specific prior written permission.

        THIS SOFTWARE IS PROVIDED BY THE COPYRIGHT HOLDERS AND CONTRIBUTORS
        'AS IS' AND ANY EXPRESS OR IMPLIED WARRANTIES, INCLUDING, BUT NOT
        LIMITED TO, THE IMPLIED WARRANTIES OF MERCHANTABILITY AND FITNESS
        FOR A PARTICULAR PURPOSE ARE DISCLAIMED. IN NO EVENT SHALL THE
        COPYRIGHT HOLDER OR CONTRIBUTORS BE LIABLE FOR ANY DIRECT, INDIRECT,
        INCIDENTAL, SPECIAL, EXEMPLARY, OR CONSEQUENTIAL DAMAGES (INCLUDING,
        BUT NOT LIMITED TO, PROCUREMENT OF SUBSTITUTE GOODS OR SERVICES;
        LOSS OF USE, DATA, OR PROFITS; OR BUSINESS INTERRUPTION) HOWEVER
        CAUSED AND ON ANY THEORY OF LIABILITY, WHETHER IN CONTRACT, STRICT
        LIABILITY, OR TORT (INCLUDING NEGLIGENCE OR OTHERWISE) ARISING IN
        ANY WAY OUT OF THE USE OF THIS SOFTWARE, EVEN IF ADVISED OF THE
        POSSIBILITY OF SUCH DAMAGE.

        SPDX-License-Identifier: BSD-3-Clause";

    revision 2020-07-29 {
        description "Initial version";
    }

    opd:augment /show:show {
        opd:command vrrp {
            opd:help 'Show Virtual Router Redundancy Protocol (VRRP) information';
            opd:on-enter 'vyatta_show_vrrp.py summary';
            opd:privileged true;

            opd:command detail {
                opd:help 'Show detailed VRRP information';
                opd:on-enter 'vyatta_show_vrrp.py detail';
                opd:privileged true;
            }

            opd:command sync-group {
                opd:help 'Show VRRP sync-group information';
                opd:on-enter 'vyatta_show_vrrp.py sync';
                opd:privileged true;

                opd:argument sync-group-name {
                    opd:help 'Show VRRP sync-group for specified group';
                    opd:allowed 'vyatta_show_vrrp.py autocomplete --sync ALL';
                    opd:on-enter 'vyatta_show_vrrp.py sync --sync=$5';
                    opd:privileged true;
                    type string;
                }
            }

            opd:command statistics {
                opd:help 'Show Virtual Router Redundancy Protocol (VRRP) statistics';
                opd:on-enter 'vyatta_show_vrrp.py stats';
                opd:privileged true;

                opd:command interface {
                    opd:help 'Show VRRP statistics for specified interface';

                    opd:argument if-name {
                        opd:help 'Show VRRP statistics for specified interface';
                        opd:allowed 'vyatta_show_vrrp.py autocomplete';
                        opd:on-enter 'vyatta_show_vrrp.py stats --intf=$5';
                        opd:privileged true;
                        type string;

                        opd:command group {
                            opd:help 'Show vrrp statistics for specified interface and group';

                            opd:argument vrid {
                                opd:help 'Show vrrp statistics for specified interface and group';
                                opd:allowed 'vyatta_show_vrrp.py autocomplete --intf=$5';
                                opd:on-enter 'vyatta_show_vrrp.py stats --intf=$5 --vrid=$7';
                                opd:privileged true;
                                type uint8{
                                    range 1..255;
                                }
                            }
                        }
                    }
                }
            }

            opd:command interface {
                opd:help 'Show VRRP information for specified interface';

                opd:argument if-name {
                    opd:help 'Show VRRP information for specified interface';
                    opd:allowed 'vyatta_show_vrrp.py autocomplete';
                    opd:on-enter 'vyatta_show_vrrp.py interface --intf=$4';
                    opd:privileged true;
                    type string;

                    opd:option group {
                        opd:help 'Show vrrp information for specified interface and group';
                        opd:allowed 'vyatta_show_vrrp.py autocomplete --intf=$4';
                        opd:on-enter 'vyatta_show_vrrp.py interface --intf=$4 --vrid=$6';
                        opd:privileged true;
                        type uint8{
                            range 1..255;
                        }
                    }
                }
            }
        }
    }

    opd:augment /show:show/log:log {
        opd:command vrrp {
            opd:help 'Show log for Virtual Router Redundancy Protocol (VRRP)';
            opd:on-enter 'journalctl -a --no-pager | grep -e Keepalived_vrrp';
        }
    }
}
