module vyatta-vrrp-state-v1 {
    namespace "urn:vyatta.com:mgmt:vyatta-vrrp-state:1";
    prefix vyatta-vrrp-state-v1;

    organization "AT&T, Inc.";
    contact
        "AT&T
        Postal: 208 S. Akard Street
        Dallas, TX 25202
        E-mail: DL-vyatta-help@att.com
        Web: www.att.com";

    description
        "Copyright (c) 2019 AT&T Intellectual Property
        All rights reserved.

        Redistribution and use in source and binary forms, with or without
        modification, are permitted provided that the following conditions
        are met:

        1. Redistributions of source code must retain the above copyright
           notice, this list of conditions and the following disclaimer.
        2. Redistributions in binary form must reproduce the above
           copyright notice, this list of conditions and the following
           disclaimer in the documentation and/or other materials provided
           with the distribution.
        3. Neither the name of the copyright holder nor the names of its
           contributors may be used to endorse or promote products derived
           from this software without specific prior written permission.

        THIS SOFTWARE IS PROVIDED BY THE COPYRIGHT HOLDERS AND CONTRIBUTORS
        'AS IS' AND ANY EXPRESS OR IMPLIED WARRANTIES, INCLUDING, BUT NOT
        LIMITED TO, THE IMPLIED WARRANTIES OF MERCHANTABILITY AND FITNESS
        FOR A PARTICULAR PURPOSE ARE DISCLAIMED. IN NO EVENT SHALL THE
        COPYRIGHT HOLDER OR CONTRIBUTORS BE LIABLE FOR ANY DIRECT, INDIRECT,
        INCIDENTAL, SPECIAL, EXEMPLARY, OR CONSEQUENTIAL DAMAGES (INCLUDING,
        BUT NOT LIMITED TO, PROCUREMENT OF SUBSTITUTE GOODS OR SERVICES;
        LOSS OF USE, DATA, OR PROFITS; OR BUSINESS INTERRUPTION) HOWEVER
        CAUSED AND ON ANY THEORY OF LIABILITY, WHETHER IN CONTRACT, STRICT
        LIABILITY, OR TORT (INCLUDING NEGLIGENCE OR OTHERWISE) ARISING IN
        ANY WAY OUT OF THE USE OF THIS SOFTWARE, EVEN IF ADVISED OF THE
        POSSIBILITY OF SUCH DAMAGE.

        SPDX-License-Identifier: BSD-3-Clause

        Add state nodes for VRRP groups";

    revision 2019-12-06 {
        description "Initial revision.";
    }

    grouping vrrp-group-state {
        container instance-state {
            config false;
            description "Simple state values for the VRRP group
                instance";
            leaf state {
                description "Current FSM state of the group";
                type enumeration {
                    enum "INIT" {
                        description "Initial state - start up";
                    }
                    enum "BACKUP"{
                        description "Backup state - listening";
                    }
                    enum "MASTER" {
                        description "Master state - transmitting";
                    }
                    enum "FAULT" {
                        description "Fault state - interface of group disabled";
                    }
                    enum "UNKNOWN" {
                        description "Transient state - should clear up";
                    }
                }
            }
            leaf rfc-interface {
                type string;
                description "Name of the created rfc interface";
            }
            leaf address-owner {
                type boolean;
                description "Indicate if this group is an address owner";
            }
            leaf last-transition {
                type uint32;
                description "Last transition time (time since epoch)";
            }
            leaf sync-group {
                type string;
                description "Name of the sync group the instance belongs to";
            }
        }
    }
}
