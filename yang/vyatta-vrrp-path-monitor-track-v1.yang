module vyatta-vrrp-path-monitor-track-v1 {
	namespace "urn:vyatta.com:mgmt:vyatta-vrrp-track:1";
	prefix vyatta-vrrp-path-monitor-track-v1;

	import configd-v1 {
		prefix configd;
	}
	import vyatta-vrrp-v1 {
		prefix vrrp;
	}
	import vyatta-services-v1 {
		prefix service;
	}
	import vyatta-service-path-monitor-v1 {
		prefix pathmon;
	}

	organization "AT&T, Inc.";
	contact
		"AT&T
		Postal: 208 S. Akard Street
		Dallas, TX 75202
		E-mail: DL-vyatta-help@att.com
		Web: www.att.com";

	description
		"Copyright (c) 2017,2019 AT&T Intellectual Property
		All rights reserved.

		Enhanced tracking for VRRP groups.

		Redistribution and use in source and binary forms, with or without
		modification, are permitted provided that the following conditions
		are met:

		1. Redistributions of source code must retain the above copyright
		   notice, this list of conditions and the following disclaimer.
		2. Redistributions in binary form must reproduce the above
		   copyright notice, this list of conditions and the following
		   disclaimer in the documentation and/or other materials provided
		   with the distribution.
		3. Neither the name of the copyright holder nor the names of its
		   contributors may be used to endorse or promote products derived
		   from this software without specific prior written permission.

		THIS SOFTWARE IS PROVIDED BY THE COPYRIGHT HOLDERS AND CONTRIBUTORS
		'AS IS' AND ANY EXPRESS OR IMPLIED WARRANTIES, INCLUDING, BUT NOT
		LIMITED TO, THE IMPLIED WARRANTIES OF MERCHANTABILITY AND FITNESS
		FOR A PARTICULAR PURPOSE ARE DISCLAIMED. IN NO EVENT SHALL THE
		COPYRIGHT HOLDER OR CONTRIBUTORS BE LIABLE FOR ANY DIRECT, INDIRECT,
		INCIDENTAL, SPECIAL, EXEMPLARY, OR CONSEQUENTIAL DAMAGES (INCLUDING,
		BUT NOT LIMITED TO, PROCUREMENT OF SUBSTITUTE GOODS OR SERVICES;
		LOSS OF USE, DATA, OR PROFITS; OR BUSINESS INTERRUPTION) HOWEVER
		CAUSED AND ON ANY THEORY OF LIABILITY, WHETHER IN CONTRACT, STRICT
		LIABILITY, OR TORT (INCLUDING NEGLIGENCE OR OTHERWISE) ARISING IN
		ANY WAY OUT OF THE USE OF THIS SOFTWARE, EVEN IF ADVISED OF THE
		POSSIBILITY OF SUCH DAMAGE.

		SPDX-License-Identifier: BSD-3-Clause";

	revision 2017-09-26 {
		description "Initial revision.";
	}

	grouping vrrp-track-pathmon {
		container path-monitor {
			description "Configure an association of policy/monitors to
				track and adjust VRRP priorities";
			configd:help "Path Monitor tracking config";
			list monitor {
				description "Name of the monitor to track";
				configd:help "Monitor to track";
				key name;
				leaf name {
					description "The name of the configured Path Monitor monitor";
					configd:help "Monitor name";

					type leafref {
						path "/service:service/pathmon:path-monitor"+
						"/pathmon:monitor/pathmon:name";
					}
				}
				list policy {
					description
						"The policies attached to the monitor, policies
						must already be attached to the monitor instance.";
					configd:help "Policy that is paired with monitor";
					min-elements 1;
					key name;
					leaf name {
						type leafref {
							path "/service:service/pathmon:path-monitor"+
							"/pathmon:monitor"+
							"[pathmon:name = current()/../../../monitor/name]"+
							"/pathmon:policy";
						}
					}
					uses vrrp:track-weight;
				}
			}
		}
	}
}
