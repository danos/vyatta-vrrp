module vyatta-vrrp-route-to-track-interfaces-dataplane-v1 {
	namespace "urn:vyatta.com:mgmt:vyatta-vrrp-route-to-track-interfaces-dataplane:1";
	prefix vyatta-vrrp-route-to-track-interfaces-dataplane-v1;

	import vyatta-interfaces-v1 {
		prefix if;
	}
	import vyatta-interfaces-dataplane-v1 {
		prefix intf-dp;
	}
	import vyatta-vrrp-v1 {
		prefix vrrp;
	}
	import vyatta-vrrp-route-to-track-v1 {
		prefix vrrp-track;
	}

	organization "AT&T Inc.";
	contact
		"AT&T
		Postal: 208 S. Akard Street
		Dallas, TX 75202
		E-mail: DL-vyatta-help@att.com
		Web: www.att.com";

	description
		"Copyright (c) 2019 AT&T Intellectual Property
		All rights reserved.

		Augment enhanced tracking on dataplane VRRP groups with route-to tracking.

		Redistribution and use in source and binary forms, with or without
		modification, are permitted provided that the following conditions
		are met:

		1. Redistributions of source code must retain the above copyright
		   notice, this list of conditions and the following disclaimer.
		2. Redistributions in binary form must reproduce the above
		   copyright notice, this list of conditions and the following
		   disclaimer in the documentation and/or other materials provided
		   with the distribution.
		3. Neither the name of the copyright holder nor the names of its
		   contributors may be used to endorse or promote products derived
		   from this software without specific prior written permission.

		THIS SOFTWARE IS PROVIDED BY THE COPYRIGHT HOLDERS AND CONTRIBUTORS
		'AS IS' AND ANY EXPRESS OR IMPLIED WARRANTIES, INCLUDING, BUT NOT
		LIMITED TO, THE IMPLIED WARRANTIES OF MERCHANTABILITY AND FITNESS
		FOR A PARTICULAR PURPOSE ARE DISCLAIMED. IN NO EVENT SHALL THE
		COPYRIGHT HOLDER OR CONTRIBUTORS BE LIABLE FOR ANY DIRECT, INDIRECT,
		INCIDENTAL, SPECIAL, EXEMPLARY, OR CONSEQUENTIAL DAMAGES (INCLUDING,
		BUT NOT LIMITED TO, PROCUREMENT OF SUBSTITUTE GOODS OR SERVICES;
		LOSS OF USE, DATA, OR PROFITS; OR BUSINESS INTERRUPTION) HOWEVER
		CAUSED AND ON ANY THEORY OF LIABILITY, WHETHER IN CONTRACT, STRICT
		LIABILITY, OR TORT (INCLUDING NEGLIGENCE OR OTHERWISE) ARISING IN
		ANY WAY OUT OF THE USE OF THIS SOFTWARE, EVEN IF ADVISED OF THE
		POSSIBILITY OF SUCH DAMAGE.

		SPDX-License-Identifier: BSD-3-Clause";

	revision 2019-07-22 {
		description	"Initial revision.";
	}

	augment /if:interfaces/intf-dp:dataplane/vrrp:vrrp/vrrp:vrrp-group/vrrp:track {
		uses vrrp-track:vrrp-track-route-to;
	}
	augment /if:interfaces/intf-dp:dataplane/intf-dp:vif/vrrp:vrrp/vrrp:vrrp-group/vrrp:track {
		uses vrrp-track:vrrp-track-route-to;
	}
}
